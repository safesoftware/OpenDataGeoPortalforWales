FME workspace WalesDataDistribution.fmw
Title: none2none

Parameters:
- COORDSYS = EPSG:27700   # British National Grid,EPSG:27700%WGS84, Latitude-Longitude,EPSG:4326 Output Coordinate System
- GENERIC_FORMAT = OGCKML
- FEATURE_TYPES = NRW_MARINE_CHARACTER_AREAS
- GEOM = POLYGON((-4.397570800781147 51.59588743997392,-5.617053222656088 51.64022666229959,-5.529162597656092 52.68475260412076,-3.4692260742186933 52.337062494805366,-3.4692260742186933 52.337062494805366,-4.397570800781147 51.59588743997392))   # " " Area of Interest

Readers:
- NULL_1: NULL
- WFS_1: WFS from http://lle.gov.wales/services/wfs/nrw

Writers:
- GENERIC_1: GENERIC to C:\Users\Administrator\Desktop in $(COORDSYS)

NRW_MARINE_CHARACTER_AREAS (reader WFS_1)
    attributes: gml_parent_id xml_buffer, gml_parent_property xml_buffer, gml_id xml_buffer, OBJECTID xml_int32, Area_sqm xml_int32, Area_sqm.xsi_nil xml_boolean, Eng_URL xml_buffer, Eng_URL.xsi_nil xml_boolean, MCA_No_1 xml_buffer, MCA_No_1.xsi_nil xml_boolean, MCA_Name_1 xml_buffer, MCA_Name_1.xsi_nil xml_boolean, MCA_Labe_1 xml_buffer, MCA_Labe_1.xsi_nil xml_boolean, MCA_Welsh xml_buffer, MCA_Welsh.xsi_nil xml_boolean
    -> Clipper_2 [CLIPPEE]
NRW_ART17_ESTUARIES (reader WFS_1)
    attributes: gml_parent_id xml_buffer, gml_parent_property xml_buffer, gml_id xml_buffer, objectid xml_buffer, feature_group xml_buffer, feature_group.xsi_nil xml_boolean, feature xml_buffer, feature.xsi_nil xml_boolean, feature_component xml_buffer, feature_component.xsi_nil xml_boolean, status xml_buffer, status.xsi_nil xml_boolean, feature_confidence xml_buffer, feature_confidence.xsi_nil xml_boolean, record_date xml_buffer, record_date.xsi_nil xml_boolean, date_of_last_edit xml_buffer, date_of_last_edit.xsi_nil xml_boolean, source xml_buffer, source.xsi_nil xml_boolean, sac_feature xml_buffer, sac_feature.xsi_nil xml_boolean, shape_area xml_buffer, shape_area.xsi_nil xml_boolean, shape_len xml_buffer, shape_len.xsi_nil xml_boolean
    -> Clipper_3 [CLIPPEE]
NRW_ART17_Mudflats_Sandflats (reader WFS_1)
    attributes: gml_parent_id xml_buffer, gml_parent_property xml_buffer, gml_id xml_buffer, objectid xml_buffer, polygonid xml_buffer, polygonid.xsi_nil xml_boolean, feature_group xml_buffer, feature_group.xsi_nil xml_boolean, feature xml_buffer, feature.xsi_nil xml_boolean, phase1_siteid xml_buffer, phase1_siteid.xsi_nil xml_boolean, phase1_siteno xml_buffer, phase1_siteno.xsi_nil xml_boolean, phase1_biotopeid xml_buffer, phase1_biotopeid.xsi_nil xml_boolean, jncc_2004_code xml_buffer, jncc_2004_code.xsi_nil xml_boolean, mncr_97_biotope xml_buffer, mncr_97_biotope.xsi_nil xml_boolean, lifeform xml_buffer, lifeform.xsi_nil xml_boolean, areaha xml_buffer, areaha.xsi_nil xml_boolean, artificial xml_buffer, artificial.xsi_nil xml_boolean, artificial_type xml_buffer, artificial_type.xsi_nil xml_boolean, nationally_important xml_buffer, nationally_important.xsi_nil xml_boolean,
      specialised xml_buffer, specialised.xsi_nil xml_boolean, bap_habitat xml_buffer, bap_habitat.xsi_nil xml_boolean, date_first_visit xml_buffer, date_first_visit.xsi_nil xml_boolean, date_last_visit xml_buffer, date_last_visit.xsi_nil xml_boolean, classification xml_buffer, classification.xsi_nil xml_boolean, owner xml_buffer, owner.xsi_nil xml_boolean, data_type xml_buffer, data_type.xsi_nil xml_boolean, substrata xml_buffer, substrata.xsi_nil xml_boolean, mixed_shore xml_buffer, mixed_shore.xsi_nil xml_boolean, status xml_buffer, status.xsi_nil xml_boolean, confidence xml_buffer, confidence.xsi_nil xml_boolean, source xml_buffer, source.xsi_nil xml_boolean, spherical_area_ha xml_buffer, spherical_area_ha.xsi_nil xml_boolean, shape_area xml_buffer, shape_area.xsi_nil xml_boolean, shape_len xml_buffer, shape_len.xsi_nil xml_boolean
    -> Clipper_4 [CLIPPEE]
NRW_HISTORIC_FLOODMAP (reader WFS_1)
    attributes: gml_parent_id xml_buffer, gml_parent_property xml_buffer, gml_id xml_buffer, OBJECTID_1 xml_int32, OBJECTID_1.xsi_nil xml_boolean, LAYER xml_buffer, LAYER.xsi_nil xml_boolean, OBJECTID xml_int32, NAME xml_buffer, NAME.xsi_nil xml_boolean, COMMENTS xml_buffer, COMMENTS.xsi_nil xml_boolean, START_DATE xml_date, START_DATE.xsi_nil xml_boolean, END_DATE xml_date, END_DATE.xsi_nil xml_boolean, FLOOD_SOURCE_TYPE xml_buffer, FLOOD_SOURCE_TYPE.xsi_nil xml_boolean, FLOOD_SOURCE_TYPE_RESOLVED xml_buffer, FLOOD_SOURCE_TYPE_RESOLVED.xsi_nil xml_boolean, FLOOD_CAUSE xml_buffer, FLOOD_CAUSE.xsi_nil xml_boolean, FLOOD_CAUSE_RESOLVED xml_buffer, FLOOD_CAUSE_RESOLVED.xsi_nil xml_boolean, FLOOD_MAP_STATUS xml_buffer, FLOOD_MAP_STATUS.xsi_nil xml_boolean, FLOOD_MAP_STATUS_RESOLVED xml_buffer, FLOOD_MAP_STATUS_RESOLVED.xsi_nil xml_boolean, HFM_STATUS xml_buffer, HFM_STATUS.xsi_nil xml_boolean,
      HFM_STATUS_RESOLVED xml_buffer, HFM_STATUS_RESOLVED.xsi_nil xml_boolean, DATA_SOURCE xml_buffer, DATA_SOURCE.xsi_nil xml_boolean, DATA_SOURCE_RESOLVED xml_buffer, DATA_SOURCE_RESOLVED.xsi_nil xml_boolean, FLOOD_TYPE_FLUVIAL xml_buffer, FLOOD_TYPE_FLUVIAL.xsi_nil xml_boolean, FLOOD_TYPE_FLUVIAL_RESOLVED xml_buffer, FLOOD_TYPE_FLUVIAL_RESOLVED.xsi_nil xml_boolean, FLOOD_TYPE_COASTAL xml_buffer, FLOOD_TYPE_COASTAL.xsi_nil xml_boolean, FLOOD_TYPE_COASTAL_RESOLVED xml_buffer, FLOOD_TYPE_COASTAL_RESOLVED.xsi_nil xml_boolean, FLOOD_TYPE_TIDAL xml_buffer, FLOOD_TYPE_TIDAL.xsi_nil xml_boolean, FLOOD_TYPE_TIDAL_RESOLVED xml_buffer, FLOOD_TYPE_TIDAL_RESOLVED.xsi_nil xml_boolean
    -> Clipper_5 [CLIPPEE]
NRW_WALES_COASTAL_PATH (reader WFS_1)
    attributes: gml_parent_id xml_buffer, gml_parent_property xml_buffer, gml_id xml_buffer, OBJECTID xml_int32, OBJECTID.xsi_nil xml_boolean, LOCALAUTHO xml_buffer, LOCALAUTHO.xsi_nil xml_boolean, STATUS xml_buffer, STATUS.xsi_nil xml_boolean, LENGTH xml_buffer, LENGTH.xsi_nil xml_boolean, GlobalID xml_buffer, GlobalID.xsi_nil xml_boolean
    -> Clipper_6 [CLIPPEE]
NRW_ART17_SEA_CAVE (reader WFS_1)
    attributes: gml_parent_id xml_buffer, gml_parent_property xml_buffer, gml_id xml_buffer, objectid xml_buffer, surveyname xml_buffer, surveyname.xsi_nil xml_boolean, copyright xml_buffer, copyright.xsi_nil xml_boolean, eventname xml_buffer, eventname.xsi_nil xml_boolean, eventreference xml_buffer, eventreference.xsi_nil xml_boolean, eventdate xml_buffer, eventdate.xsi_nil xml_boolean, coordinatesystem xml_buffer, coordinatesystem.xsi_nil xml_boolean, latwgs84 xml_buffer, latwgs84.xsi_nil xml_boolean, longwgs84 xml_buffer, longwgs84.xsi_nil xml_boolean, sample_reference xml_buffer, sample_reference.xsi_nil xml_boolean, habitat xml_buffer, habitat.xsi_nil xml_boolean, biotopecode xml_buffer, biotopecode.xsi_nil xml_boolean, targetnote xml_buffer, targetnote.xsi_nil xml_boolean, source xml_buffer, source.xsi_nil xml_boolean
    -> Reprojector_3
Note: Reproject from map coordinate / system to features coordinate / system.
Reprojector_3
    DEST = EPSG:27700
    INTERPOLATION_TYPE_NAME = Nearest Neighbor
    RASTER_CELL_SIZE = Preserve Cells
    RASTER_TOLERANCE = 0.0
    SOURCE = EPSG:4326
    REPROJECTED -> Clipper_7 [CLIPPEE]
Creator
    GEOMTYPE = Geometry Object
    NUM = 1
    CREATED -> GeometryReplacer
GeometryReplacer
    KIND_LONG = OGC Well Known Text
    OGC_WKT_PRECISION_DISPLAY = 64-bit
    REMOVE_ATTRIBUTE = No
    SOURCE = $(GEOM)
    -> Reprojector_2
Note: Reproject from map coordinate / system to features coordinate / system.
Reprojector_2
    DEST = EPSG:27700
    INTERPOLATION_TYPE_NAME = Nearest Neighbor
    RASTER_CELL_SIZE = Preserve Cells
    RASTER_TOLERANCE = 0.0
    SOURCE = LL84
    REPROJECTED -> Clipper_2 [CLIPPER]
    REPROJECTED -> Clipper_3 [CLIPPER]
    REPROJECTED -> Clipper_4 [CLIPPER]
    REPROJECTED -> Clipper_5 [CLIPPER]
    REPROJECTED -> Clipper_6 [CLIPPER]
    REPROJECTED -> Clipper_7 [CLIPPER]
KMLPropertySetter_3
    ADD_ATTR_TABLE = Yes
    ALTITUDE_MODE = Clamp To Sea Floor
    ATTR_TABLE_TITLE = Attributes
    CONTENT = @Value(MCA_Labe_1)
    CONTENT_TYPE = Text
    EXTRUDE = No
    GEOM_TYPE = Vector
    NAME = <auto>
    SUMMARY = <none>
    TESSELATE = Yes
    VISIBILITY = Yes
    -> KMLStyler_6
KMLStyler_6
    COLOR = 1,1,1
    FILL_COLOR = 0,0,0.905882
    FILL_OPACITY = 0.4
    ICON_OPACITY = 1.0
    ICON_SCALE = 0.8
    LABEL_OPACITY = 1.0
    LABEL_SCALE = 1.0
    LABEL_VISIBILITY = Yes
    LINE_WIDTH = 3
    LINE_WIDTH_UNITS = Pixels (Display Units)
    OPACITY = 1.0
    STYLE_PER_FEATURE = Yes
    KMLStyled -> NRW – Marine Character Areas (writer GENERIC_1)
NRW – Marine Character Areas (writer GENERIC_1)
    attributes: gml_parent_id buffer, gml_parent_property buffer, OBJECTID int32, Area_sqm int32, Eng_URL buffer, MCA_No_1 buffer, MCA_Name_1 buffer, MCA_Labe_1 buffer, MCA_Welsh buffer, _clipped varchar(200)
KMLPropertySetter_4
    ADD_ATTR_TABLE = Yes
    ALTITUDE_MODE = Clamp To Sea Floor
    ATTR_TABLE_TITLE = Attributes
    CONTENT = @Value(feature_component)
    CONTENT_TYPE = Text
    EXTRUDE = No
    GEOM_TYPE = Vector
    NAME = <auto>
    SUMMARY = <none>
    TESSELATE = Yes
    VISIBILITY = Yes
    -> NRW – Article 17 – Estuaries (writer GENERIC_1)
NRW – Article 17 – Estuaries (writer GENERIC_1)
    attributes: gml_parent_property buffer, gml_id buffer, objectid buffer, feature_group buffer, feature buffer, feature_component buffer, status buffer, feature_confidence buffer, record_date buffer, date_of_last_edit buffer, source buffer, sac_feature buffer, shape_area buffer, shape_len buffer, _clipped varchar(200)
KMLPropertySetter_5
    ADD_ATTR_TABLE = Yes
    ALTITUDE_MODE = Clamp To Sea Floor
    ATTR_TABLE_TITLE = Attributes
    CONTENT = @Value(feature)
    CONTENT_TYPE = Text
    EXTRUDE = No
    GEOM_TYPE = Vector
    NAME = <auto>
    SUMMARY = <none>
    TESSELATE = Yes
    VISIBILITY = Yes
    -> NRW – Article 17 – Mudflats and Sandflats (writer GENERIC_1)
NRW – Article 17 – Mudflats and Sandflats (writer GENERIC_1)
    attributes: gml_parent_property buffer, gml_id buffer, objectid buffer, polygonid buffer, feature_group buffer, feature buffer, phase1_siteid buffer, phase1_siteno buffer, phase1_biotopeid buffer, jncc_2004_code buffer, mncr_97_biotope buffer, lifeform buffer, areaha buffer, artificial buffer, artificial_type buffer, nationally_important buffer, specialised buffer, bap_habitat buffer, date_first_visit buffer, date_last_visit buffer, classification buffer, owner buffer, data_type buffer, substrata buffer, mixed_shore buffer, status buffer, confidence buffer, source buffer, spherical_area_ha buffer, shape_area buffer,
      shape_len buffer, _clipped varchar(200)
KMLPropertySetter_6
    ADD_ATTR_TABLE = Yes
    ATTR_TABLE_TITLE = Attributes
    CONTENT = @Value(COMMENTS)
    CONTENT_TYPE = Text
    EXTRUDE = No
    GEOM_TYPE = Vector
    NAME = <auto>
    SUMMARY = <none>
    TESSELATE = Yes
    VISIBILITY = Yes
    -> NRW – Historic Flood Outlines (writer GENERIC_1)
NRW – Historic Flood Outlines (writer GENERIC_1)
    attributes: gml_parent_property buffer, gml_id buffer, OBJECTID_1 int32, LAYER buffer, OBJECTID int32, NAME buffer, COMMENTS buffer, START_DATE buffer, END_DATE buffer, FLOOD_SOURCE_TYPE buffer, FLOOD_SOURCE_TYPE_RESOLVED buffer, FLOOD_SOURCE_TYPE_RESOLVED.xsi_nil boolean, FLOOD_CAUSE buffer, FLOOD_CAUSE_RESOLVED buffer, FLOOD_CAUSE_RESOLVED.xsi_nil boolean, FLOOD_MAP_STATUS buffer, FLOOD_MAP_STATUS_RESOLVED buffer, FLOOD_MAP_STATUS_RESOLVED.xsi_nil boolean, HFM_STATUS buffer, HFM_STATUS.xsi_nil boolean, HFM_STATUS_RESOLVED buffer, DATA_SOURCE buffer, DATA_SOURCE_RESOLVED buffer, DATA_SOURCE_RESOLVED.xsi_nil boolean, FLOOD_TYPE_FLUVIAL buffer, FLOOD_TYPE_FLUVIAL_RESOLVED buffer, FLOOD_TYPE_FLUVIAL_RESOLVED.xsi_nil boolean, FLOOD_TYPE_COASTAL buffer, FLOOD_TYPE_COASTAL_RESOLVED buffer, FLOOD_TYPE_COASTAL_RESOLVED.xsi_nil boolean,
      FLOOD_TYPE_TIDAL buffer, FLOOD_TYPE_TIDAL_RESOLVED buffer, FLOOD_TYPE_TIDAL_RESOLVED.xsi_nil boolean, _clipped varchar(200)
KMLPropertySetter_7
    ADD_ATTR_TABLE = Yes
    ATTR_TABLE_TITLE = Attributes
    CONTENT = @Value(LOCALAUTHO)
    CONTENT_TYPE = Text
    EXTRUDE = No
    GEOM_TYPE = Vector
    NAME = <auto>
    SUMMARY = <none>
    TESSELATE = Yes
    VISIBILITY = Yes
    -> NRW – Wales Coastal Path (writer GENERIC_1)
NRW – Wales Coastal Path (writer GENERIC_1)
    attributes: gml_parent_property buffer, gml_id buffer, OBJECTID int32, LOCALAUTHO buffer, LOCALAUTHO.xsi_nil boolean, STATUS buffer, LENGTH buffer, GlobalID buffer, _clipped varchar(200)
KMLPropertySetter_8
    ADD_ATTR_TABLE = Yes
    ATTR_TABLE_TITLE = Attributes
    CONTENT = @Value(eventname)
    CONTENT_TYPE = Text
    EXTRUDE = No
    GEOM_TYPE = Vector
    NAME = @Value(eventname)
    SUMMARY = <none>
    TESSELATE = Yes
    VISIBILITY = Yes
    -> KMLStyler_5
KMLStyler_5
    FILL_OPACITY = 0.4
    ICON_COLOR = 0,0,0
    ICON_NAME = B1
    ICON_OPACITY = 1.0
    ICON_SCALE = 0.8
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes
    KMLStyled -> NRW – Article 17 – Sea Caves (writer GENERIC_1)
NRW – Article 17 – Sea Caves (writer GENERIC_1)
    attributes: gml_parent_id buffer, gml_parent_property buffer, gml_id buffer, objectid buffer, surveyname buffer, copyright buffer, eventname buffer, eventreference buffer, eventdate buffer, eventdate.xsi_nil boolean, coordinatesystem buffer, latwgs84 buffer, longwgs84 buffer, sample_reference buffer, habitat buffer, biotopecode buffer, targetnote buffer, source buffer, _clipped varchar(200)

Bookmark: Army of Clippers
Clipper_2
    BOUNDARY_CASES = Treat as Inside
    CLEANING_TOLERANCE = None
    CLIPPED_ATTR = _clipped
    CLIP_TYPE = Single Clipper
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clipper and Clippee
    INSIDE -> KMLPropertySetter_3
    INSIDE -> Clipper_2_:_Inside
Clipper_2_:_Inside: Inspector [off]
Clipper_3
    BOUNDARY_CASES = Treat as Inside
    CLEANING_TOLERANCE = None
    CLIPPED_ATTR = _clipped
    CLIP_TYPE = Single Clipper
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clipper and Clippee
    INSIDE -> KMLPropertySetter_4
Clipper_4
    BOUNDARY_CASES = Treat as Inside
    CLEANING_TOLERANCE = None
    CLIPPED_ATTR = _clipped
    CLIP_TYPE = Single Clipper
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clipper and Clippee
    INSIDE -> KMLPropertySetter_5
Clipper_5
    BOUNDARY_CASES = Treat as Inside
    CLEANING_TOLERANCE = None
    CLIPPED_ATTR = _clipped
    CLIP_TYPE = Single Clipper
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clipper and Clippee
    INSIDE -> KMLPropertySetter_6
Clipper_6
    BOUNDARY_CASES = Treat as Inside
    CLEANING_TOLERANCE = None
    CLIPPED_ATTR = _clipped
    CLIP_TYPE = Single Clipper
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clipper and Clippee
    INSIDE -> KMLPropertySetter_7
Clipper_7
    BOUNDARY_CASES = Treat as Inside
    CLEANING_TOLERANCE = None
    CLIPPED_ATTR = _clipped
    CLIP_TYPE = Single Clipper
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clipper and Clippee
    INSIDE -> KMLPropertySetter_8

Bookmark: Style Individual Feature Types for KML Output
FeatureTypeFilter [off]
    ATTRIBUTES = <BLANK>,<UNFILTERED>,SkytrainStations,BusStops,SkytrainLines,BusRoutes
    SkytrainStations -> KMLStyler
    BusStops -> KMLStyler_2
    SkytrainLines -> KMLStyler_3
    BusRoutes -> KMLStyler_4
KMLStyler [off]
    FILL_OPACITY = 0.4
    ICON_COLOR = 1,0,0
    ICON_OPACITY = 1.0
    ICON_SCALE = 0.8
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes
    KMLStyled -> KMLPropertySetter
KMLPropertySetter [off]
    ADD_ATTR_TABLE = Yes
    ATTR_TABLE_TITLE = Attributes
    CONTENT_TYPE = Text
    EXTRUDE = No
    GEOM_TYPE = Vector
    NAME = @Value(StationName)
    TESSELATE = Yes
    VISIBILITY = Yes
    -> AttributeExposer
KMLStyler_2 [off]
    FILL_OPACITY = 0.4
    ICON_COLOR = 1,0.500008,0
    ICON_OPACITY = 1.0
    ICON_SCALE = 0.8
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes
    KMLStyled -> KMLPropertySetter_2
KMLPropertySetter_2 [off]
    ADD_ATTR_TABLE = Yes
    ATTR_TABLE_TITLE = Attributes
    CONTENT_TYPE = Text
    EXTRUDE = No
    GEOM_TYPE = Vector
    NAME = @Value(StopNumber)
    TESSELATE = Yes
    VISIBILITY = Yes
    -> AttributeExposer
KMLStyler_3 [off]
    COLOR = 1,0.666667,0
    FILL_OPACITY = 0.4
    ICON_OPACITY = 1.0
    ICON_SCALE = 0.8
    LABEL_OPACITY = 1.0
    LABEL_SCALE = 1.0
    LABEL_VISIBILITY = Yes
    LINE_WIDTH = 2
    LINE_WIDTH_UNITS = Pixels (Display Units)
    OPACITY = 1.0
    STYLE_PER_FEATURE = Yes
    KMLStyled -> AttributeExposer
KMLStyler_4 [off]
    COLOR = 0.333333,0.666667,0
    FILL_OPACITY = 0.4
    ICON_OPACITY = 1.0
    ICON_SCALE = 0.8
    LABEL_OPACITY = 1.0
    LABEL_SCALE = 1.0
    LABEL_VISIBILITY = Yes
    LINE_WIDTH = 2
    LINE_WIDTH_UNITS = Pixels (Display Units)
    OPACITY = 1.0
    STYLE_PER_FEATURE = Yes
    KMLStyled -> AttributeExposer
AttributeExposer [off]
    ATTR_LIST = fme_feature_type,fme_basename
